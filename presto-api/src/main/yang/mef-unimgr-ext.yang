module mef-unimgr-ext {
  namespace "urn:mef:unimgr-ext";
  prefix mef-unimgr-ext;

  import onf-core-network-module {
    prefix onf-cn;
  }

  revision 2016-07-25 {
  }

  typedef ActivationStatus {
    type enumeration {
      enum INACTIVE;
      enum ACTIVE;
      enum FAILED;
    }
  }

  typedef CTagVlanId {
      type uint32 {
        range "0..4095";
      }
  }

  augment "/onf-cn:forwarding-constructs/onf-cn:forwarding-construct" {
    container unimgr-attrs {
      leaf status {
        type ActivationStatus;
        config false;
        default INACTIVE;
      }
    }
  }

  augment "/onf-cn:forwarding-constructs/onf-cn:forwarding-construct/onf-cn:fcPort" {
      leaf cTagVlanId {
        type CTagVlanId;
        config true;
        default 0;
      }
   }
}
